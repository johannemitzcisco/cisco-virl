module cisco-virl-stats {

  namespace "http://com/example/ciscovirl-stats";
  prefix cisco-virlstats;

  import tailf-common { prefix tailf; }
  import cisco-virl { prefix cisco-virl; }

  container simulations {
    config false;
    list simulation {
      key "name";
      leaf name {
        type string;
      }
      leaf status {
        type string;
      }
      leaf launched {
        type string;
      }
      leaf expires {
        type string;
      }
      container topology {
        leaf name {
          type string;
        }
        list node {
          key name;
          leaf name {
            type string;
          }
          leaf excludeFromLaunch {
            type string;
          }
          leaf state {
            type string;
          }
          leaf reachable {
            type boolean;
          }
        }
      }
    }
  }
}
